-- Schema ID: 1
Contact-Module DEFINITIONS ::= BEGIN
    IMPORTS Recipient-Prekey-Bundle FROM Recipient-Prekey-Bundle-Module;

    Contact ::= SEQUENCE {
        version INTEGER,
        schema INTEGER,

        label UTF8String,
        memo UTF8String,
        prekey-bundle Recipient-Prekey-Bundle
    }
END
