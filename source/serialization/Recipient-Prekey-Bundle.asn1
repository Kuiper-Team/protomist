Recipient-Prekey-Bundle-Module DEFINITIONS ::= BEGIN
    Recipient-Prekey-Bundle ::= SEQUENCE {
        identity-pk OCTET STRING,

        spk OCTET STRING,
        pqspk OCTET STRING,

        spk-identifier OCTET STRING,
        pqspk-identifier OCTET STRING,

        spk-signature OCTET STRING,
        pqspk-signature OCTET STRING
    }
END
